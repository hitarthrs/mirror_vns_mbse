package MirrorTradeRequirements {
    doc
    /* Requirement thresholds are authoritative and evaluated on the architecture. */

    private import RequirementsManagement::*;
    private import ScalarValues::*;
    private import MirrorTradeArchitecture::*;

    requirement def TritiumSelfSufficiency :> Requirement {
        subject blanketSystem references mirrorTradeNominal.blanket;
        attribute minimumTbr : ScalarValues::Real = 1.1;
        require constraint { blanketSystem.tritiumBreedingRatio > minimumTbr }
        :>> verificationStatus = VVStatus::NotStarted;
    }

    requirement def MinimumThermalPower :> Requirement {
        subject blanketSystem references mirrorTradeNominal.blanket;
        attribute minimumThermalPower_MW : ScalarValues::Real = 50.0;
        require constraint { blanketSystem.thermalPower_MW >= minimumThermalPower_MW }
        :>> verificationStatus = VVStatus::NotStarted;
    }

    requirement def MagnetHeatingLimit :> Requirement {
        subject magnetSystem references mirrorTradeNominal.magnets;
        attribute maximumMagnetHeating_MW_per_cc : ScalarValues::Real = 90.0;
        require constraint {
            magnetSystem.nuclearHeating_MW_per_cc <= maximumMagnetHeating_MW_per_cc
        }
        :>> verificationStatus = VVStatus::NotStarted;
    }

    requirement def CapitalCostLimit :> Requirement {
        subject plantEconomics references mirrorTradeNominal.economics;
        attribute maximumCapitalCost_Musd : ScalarValues::Real = 500.0;
        require constraint { plantEconomics.capitalCost_Musd <= maximumCapitalCost_Musd }
        :>> verificationStatus = VVStatus::NotStarted;
    }
}
